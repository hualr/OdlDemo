module odlDemo {
    yang-version 1.1;
    namespace "urn:opendaylight:params:xml:ns:yang:odlDemo";
    prefix "odlDemo";

    revision "2018-05-17" { // TODO change revision to date of model creation
        description "Initial revision of odlDemo model";
    }
}
